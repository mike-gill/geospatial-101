FME workspace fme-gridinquestreprojector.fmw

Parameters:
- SourceDataset_GEOJSON = $(FME_MF_DIR)data\ostn02\test_wgs84_ntv2.json   # Source GeoJSON File or URL
- DestDataset_SHAPE = $(FME_MF_DIR)data\ostn02   # Destination Esri Shape Folder
- DestDataset_SHAPE_3 = $(FME_MF_DIR)data\ostn02   # Destination Esri Shape Folder

Readers:
- GEOJSON_1: GEOJSON from $(SourceDataset_GEOJSON) in EPSG:4326

Writers:
- SHAPE_1: SHAPE to $(DestDataset_SHAPE)
- SHAPE_2: SHAPE to $(DestDataset_SHAPE_3) in EPSG:27700

test_wgs84_ntv2 (reader GEOJSON_1)
    attributes: prop0 string
    -> GridInQuestReprojector
    -> fme-default-reproj-osgb (writer SHAPE_2)
GridInQuestReprojector
    INTERPOLATION_TYPE_NAME = Bilinear
    DEST_CS_NAME = OSGB36 (OSTN02)
    SOURCE_CS_NAME = ETRS89 Geodetic (ellipsoid height)
    RASTER_CELL_SIZE = Preserve Cells
    REPROJECTED -> fme-gridinquest-osgb (writer SHAPE_1)
fme-gridinquest-osgb (writer SHAPE_1)
    attributes: prop0 char(20)
fme-default-reproj-osgb (writer SHAPE_2)
    attributes: prop0 char(20)
